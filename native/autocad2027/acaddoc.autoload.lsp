;;; acaddoc.autoload.lsp
;;; ---------------------------------------------------------------------------
;;; All-In-Cad AutoCAD 2027 adapter - auto NETLOAD bootstrap.
;;;
;;; Generated by the ZWCAD 2026 -> AutoCAD 2027 port. NOT YET DEPLOYED: this file is a
;;; staged artifact. It must be copied into an AutoCAD SUPPORT PATH before it runs.
;;; The user must approve that copy; this task deliberately did not touch any
;;; AutoCAD installation directory and did not touch the running AutoCAD instance.
;;;
;;; WHERE TO COPY (pick the one AutoCAD actually reports in SUPPORTPATHA):
;;;   1. %APPDATA%\Autodesk\AutoCAD 2027\Support\            (roaming profile)
;;;   2. %USERPROFILE%\Documents\AutoCAD 2027\Support\        (default Documents)
;;;   3. any folder already listed by (getvar "TRUSTEDPATHS")
;;; Do NOT put it in D:\Program Files\AutoCAD 2027 - that is the install tree.
;;;
;;; WHAT IT DOES
;;;   1. NETLOADs the compiled AllInCad.AutoCAD2027.dll (if it is not already loaded).
;;;   2. Wraps the call in vl-catch-all-apply so a load failure CANNOT block AutoCAD
;;;      startup or leave a half-written state on the command line.
;;;   3. Appends one line to logs\acaddoc.netload.log so a silent failure is still
;;;      observable after the fact.
;;;
;;; SECURELOAD NOTES (read before changing anything)
;;;   - SECURELOAD restricts (load ...) of LISP from untrusted locations. It does NOT
;;;     block NETLOAD of a .NET assembly, so a SECURELOAD failure here is not expected.
;;;   - The DLL folder must therefore NOT be added to TRUSTEDPATHS just for this to work.
;;;     This file deliberately does not call (load ...) and does not touch TRUSTEDPATHS.
;;;   - NETLOAD may still raise the .NET assembly security prompt depending on the
;;;     machine's TRUSTEDPATHS / application settings; that prompt is a user decision and
;;;     is deliberately not auto-accepted here.
;;;
;;; UNVERIFIED: nothing in this file has been executed. It was not loaded into any
;;; AutoCAD session by the port task. Validate it by copying it in and restarting.
;;; ---------------------------------------------------------------------------

(setq *all-in-cad-dll*
       "C:/Users/khs09/all-in-cad/native/autocad2027/bin/Release/AllInCad.AutoCAD2027.dll")

(setq *all-in-cad-log*
       "C:/Users/khs09/all-in-cad/native/autocad2027/logs/acaddoc.netload.log")

;; One-shot guard: acaddoc.lsp runs again for every new drawing in the same session.
(setq *all-in-cad-netload-tried* nil)

(defun AIC-LOG (msg / f)
  (setq f (open *all-in-cad-log* "a"))
  (if f
    (progn
      (write-line (strcat (menucmd "M=$(edtime,$(getvar,DATE),HH:MM:SS)") " " msg) f)
      (close f)
    )
    (princ "\n[AIC] cannot open acaddoc log file.\n")
  )
  (princ)
)

(defun AIC-NETLOAD-ONCE
  (/ f already-loaded res err)
  ;; Already loaded in this session? Ask the .NET side, do not guess.
  (if *all-in-cad-netload-tried*
    (AIC-LOG "skipped: already attempted in this session")
    (progn
      (setq *all-in-cad-netload-tried* T)

      (if (not (findfile *all-in-cad-dll*))
        (AIC-LOG
          (strcat "SKIPPED: DLL not found at " *all-in-cad-dll*
                  " - rebuild native\\autocad2027 first"))
        (progn
          ;; vl-catch-all-apply is the whole point of this file: a .NET load failure must
          ;; not abort AutoCAD startup and must not dump a raw error on the command line.
          (setq res (vl-catch-all-apply
                      'command
                      (list "_.NETLOAD" *all-in-cad-dll*)))

          (cond
            ((not (vl-catch-all-error-p res))
              (AIC-LOG (strcat "NETLOAD dispatched: " *all-in-cad-dll*
                               " (dispatched != confirmed: AutoCAD may still prompt)")))

            (T
              (setq err (vl-catch-all-error-message res))
              (AIC-LOG (strcat "NETLOAD FAILED: " err))
              (princ
                (strcat "\n[AIC] AutoCAD2027 adapter NETLOAD failed: " err
                        "\n     dll : " *all-in-cad-dll*
                        "\n     log : " *all-in-cad-log*
                        "\n     The adapter is NOT loaded; AutoCAD continues normally."
                        "\n"))
            )
          )
        )
      )
    )
  )
  (princ)
)

;; SECURELOAD is read for reporting only - it is never changed by this file.
(AIC-LOG
  (vl-princ-to-string
    (list "acaddoc bootstrap start"
          :dll *all-in-cad-dll*
          :secureload (getvar "SECURELOAD")
          :trustedpaths (getvar "TRUSTEDPATHS")
          :acad (getvar "ACADVER"))))

(AIC-NETLOAD-ONCE)

(princ)
